# Requirements

## 7: Autonomous Flight (Functional)
The UAV shall be able to fly a preprogrammed course without pilot intervention.

## 5: Payload Data Rate (Functional)
The UAV shall support a payload data rate out of up to 20 Mb/s.

## 8: Payload Mass (Functional)
The UAV shall support a payload mass of up to 50 kg.

### 8.1: Maximum Mass (Functional)
Maximum Mass is 50 kg

### 8.2: Minimum Mass (Functional)
Minimum Mass shall be 2 kg.

## 6: Payload Power Demand (Functional)
The UAV shall support a payload power demand of up to 1 kW.
