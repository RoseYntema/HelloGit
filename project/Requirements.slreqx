# Requirements

## 4: Payload Mass (Functional)
The UAV shall support a payload mass of up to 50 kg.

### 4.1: Maximum Mass (Functional)
Maximum Mass is 50 kg

### 4.2: Minimum Mass (Functional)
Minimum Mass is 0 kg
